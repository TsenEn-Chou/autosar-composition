# TPC_Requirements

## #1: Primary Throttle Position Sensor SW-C (Functional)

## #2: Seconday Throttle Position Sensor SW-C (Functional)

## #3: Accelerator Pedal Position Sensor SW-C (Functional)

## #4: Throttle Position Actuator SW-C (Functional)
